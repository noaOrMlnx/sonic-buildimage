module sonic-copp {

	yang-version 1.1;

	namespace "http://github.com/Azure/sonic-copp";
	prefix copp;

	import sonic-types {
		prefix stypes;
	}

	description "CoPP YANG Module for SONiC OS";

	revision 2021-03-31 {
		description
			"First Revision";
	}

	container sonic-copp {
		container COPP_GROUP {
			list COPP_GROUP_LIST {
				key name;

				leaf name {
					type string;
					description "Control plane policing group name";
				}

				leaf queue {
					type uint32;
					default 0;
					description "CPU Rx queue id";
				}

				leaf trap_priority {
					type uint32;
					default 0;
					description "Trap priority";
				}

				leaf trap_action {
					mandatory true;
					type stypes:copp_packet_action;
					description "Trap action";
				}

				leaf meter_type {
					mandatory true;
					type stypes:meter_type;
					description "Policer meter type";
				}

				leaf mode {
					mandatory true;
					type enumeration {
						enum sr_tcm;
						enum tr_tcm;
						enum storm;
					}
					description "Policer mode";
				}

				leaf color {
					type enumeration {
						enum blind;
						enum color;
					}
					default "color";
					description "Policer color source";
				}

				leaf cir {
					type uint64;
					default 0;
					description
						"Committed information rate for the dual-rate token
						bucket policer.  This value represents the rate at which
						tokens are added to the primary bucket.";
				}

				leaf cbs {
					must "((current()/../cir) and (current()/../cir > 0))" {
						error-message "cbs can't be configured without cir.";
					}
					must "(current() >= current()/../cir)" {
						error-message "cbs must be greater than or equal to cir";
					}
					type uint64;
					default 0;
					description
						"Committed burst size for the dual-rate token bucket
						policer.  This value represents the depth of the token
						bucket.";
				}

				leaf pir {
					when "current()/../mode = 'tr_tcm'";
					must "((current()/../cir) and (current()/../cir > 0))" {
						error-message "pir can't be configured without cir.";
					}
					must "(current() >= current()/../cir)" {
						error-message "pir must be greater than or equal to cir";
					}
					type uint64;
					description
						"Peak information rate for the dual-rate token bucket
						policer.  This value represents the rate at which tokens
						are added to the secondary bucket.";
				}

				leaf pbs {
					when "((current()/../mode = 'sr_tcm') or (current()/../mode = 'tr_tcm'))";
					must "((not(current()/../cbs)) or (current() >= current()/../cbs))" {
						error-message "pbs must be greater than or equal to cbs";
					}
					type uint64;
					description
						"Excess burst size for the dual-rate token bucket policer.
						This value represents the depth of the secondary bucket.";
				}

				leaf green_action {
					type stypes:copp_packet_action;
					default "forward";
					description "Green action";
				}

				leaf yellow_action {
					when "((current()/../mode = 'sr_tcm') or (current()/../mode = 'tr_tcm'))";
					type stypes:copp_packet_action;
					default "forward";
					description "Yellow action";
				}

				leaf red_action {
					type stypes:copp_packet_action;
					default "forward";
					description "Red action";
				}
			}
			/* end of list COPP_GROUP_LIST */
		}
		/* end of container COPP_GROUP */

		container COPP_TRAP {
			list COPP_TRAP_LIST {
				key name;

				leaf name {
					type string;
					description "Control plane policing trap name";
				}

				leaf trap_ids {
					mandatory true;
					type string;
					description "list of trap_ids";
				}

				leaf trap_group {
					type leafref {
						path "/sonic-copp/COPP_GROUP/COPP_GROUP_LIST/name";
					}
					description "reference to CoPP group";
				}

				leaf always_enabled {
					type string;
					description "a field that indicates whether the trap should be always installed"
				}
			}
			/* end of list COPP_TRAP_LIST */
		}
		/* end of container COPP_TRAP */
	}
	/* end of top level container */

	rpc get-match-protocols {
		description
			"RPC to get allowed match protocols";

		output {
			list Match_protocols {
				key "Protocol";

				leaf Protocol {
					type string;
					description
						"Protocol name";
				}
			}
		}
	}
	/* end of rpc get-match-protocols */
}
/* end of module sonic-copp */
